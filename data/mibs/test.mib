--
-- S03B-MIB.my
-- MIB generated by MG-SOFT Visual MIB Builder Version 6.0  Build 88
-- Tuesday, March 05, 2019 at 11:19:34
--

--  S03B-MIB.my
-- MIB generated by MG-SOFT Visual MIB Builder Version 6.0  Build 88
-- Saturday, January 26, 2019 at 18:06:21
-- 

	S03B-MIB DEFINITIONS ::= BEGIN
 
		IMPORTS
			enterprises,MODULE-IDENTITY, OBJECT-TYPE, Integer32, Unsigned32,
				Gauge32, Counter32, Counter64, IpAddress, mib-2
             FROM SNMPv2-SMI
			DisplayString
					FROM SNMPv2-TC;
--  1.3.6.1.4.1.2011
-- January 24, 2019 at 09:55 GMT
		-- 1.3.6.1.4.1.2011
		zyt MODULE-IDENTITY 
			LAST-UPDATED "201901240955Z"		-- January 24, 2019 at 09:55 GMT
			ORGANIZATION 
				"ZYT"
			CONTACT-INFO 
				"hexinjun@robot-zyt.com"
			DESCRIPTION 
				"Description."
			::= { enterprises 7944 }

		
	
--
-- Node definitions
--
	
--  Node definitions
-- 
-- 1.3.6.1.4.1.2011.2
		-- 1.3.6.1.4.1.2011.2
		products OBJECT IDENTIFIER ::= { zyt 7999 }
		
--  1.3.6.1.4.1.2011.2.217.7.1.1
		-- 1.3.6.1.4.1.2011.2.217.7.1.1
		snmpBoardParameter OBJECT IDENTIFIER ::= { products 2 }

		
--  1.3.6.1.4.1.2011.2.217.7.1.1.1
		-- 1.3.6.1.4.1.2011.2.217.7.1.1.1
		softwareVersion22 OBJECT-TYPE
			SYNTAX IpAddress
			MAX-ACCESS read-only
			STATUS current
			DESCRIPTION
				"Description."
			::= { snmpBoardParameter 3 } 
		
	END

--
-- S03B-MIB.my
--
